import FreeCAD
import FreeCADGui
import Part
import json
import os
from PySide import QtGui

# ==============================================================================
# Arkhe 6D Voxel Exporter - FreeCAD Macro
# ==============================================================================
# Esta macro permite selecionar um objeto 3D no FreeCAD e exportá-lo como um
# arquivo JSON contendo Voxels 6D (Posição + Material + Tempo + Função + Fase),
# pronto para ser consumido pelo PhaseSlicer em Go.
# ==============================================================================

def export_to_arkhe():
    # 1. Obter a seleção atual
    sel = FreeCADGui.Selection.getSelection()
    if not sel:
        QtGui.QMessageBox.warning(None, "Erro", "Selecione um objeto sólido primeiro.")
        return

    obj = sel[0]
    if not hasattr(obj, "Shape") or obj.Shape.isNull():
        QtGui.QMessageBox.warning(None, "Erro", "O objeto selecionado não possui uma forma (Shape) válida.")
        return

    shape = obj.Shape

    # 2. Solicitar parâmetros 6D ao usuário
    resolution, ok = QtGui.QInputDialog.getDouble(None, "Resolução", "Tamanho do Voxel (mm):", 1.0, 0.1, 100.0, 2)
    if not ok: return

    material_id, ok = QtGui.QInputDialog.getInt(None, "Material", "ID do Material (0=Polímero, 1=Condutor):", 0, 0, 10, 1)
    if not ok: return

    elasticity, ok = QtGui.QInputDialog.getDouble(None, "Elasticidade (4D)", "Valor de Elasticidade:", 0.5, 0.0, 1.0, 3)
    if not ok: return

    conductivity, ok = QtGui.QInputDialog.getDouble(None, "Condutividade (6D)", "Valor de Condutividade:", 0.8 if material_id > 0 else 0.0, 0.0, 1.0, 3)
    if not ok: return

    target_phase, ok = QtGui.QInputDialog.getDouble(None, "Fase Alvo", "Fase Quântica Alvo (θ):", 1.57, -3.14, 3.14, 3)
    if not ok: return

    # 3. Voxelização baseada na Bounding Box
    bbox = shape.BoundBox
    voxels = []
    
    x = bbox.XMin
    while x <= bbox.XMax:
        y = bbox.YMin
        while y <= bbox.YMax:
            z = bbox.ZMin
            while z <= bbox.ZMax:
                pt = FreeCAD.Vector(x, y, z)
                # Verifica se o centro do voxel está dentro do sólido
                if shape.isInside(pt, resolution / 2.0, True):
                    voxels.append({
                        "Pos": {"X": x, "Y": y, "Z": z},
                        "MaterialID": material_id,
                        "Elasticity": elasticity,
                        "Conductivity": conductivity,
                        "TargetPhase": target_phase
                    })
                z += resolution
            y += resolution
        x += resolution

    if not voxels:
        QtGui.QMessageBox.warning(None, "Aviso", "Nenhum voxel gerado. Tente uma resolução menor.")
        return

    # 4. Salvar arquivo JSON
    filepath, _ = QtGui.QFileDialog.getSaveFileName(None, "Salvar Voxel6D JSON", os.path.expanduser("~"), "JSON Files (*.json)")
    if filepath:
        with open(filepath, 'w') as f:
            json.dump(voxels, f, indent=2)
        QtGui.QMessageBox.information(None, "Sucesso", f"Exportados {len(voxels)} voxels 6D para {filepath}")

export_to_arkhe()
